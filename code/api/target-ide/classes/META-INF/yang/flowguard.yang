module flowguard {
    yang-version 1;
    namespace "urn:opendaylight:params:xml:ns:yang:flowguard";
    prefix "flowguard";

    revision "2017-09-13" {
        description "Initial revision of flowguard model";
    }

    grouping fwrule {
        leaf ruleId {
           type uint16;
           config true;
           mandatory true;
           description "Name of FW rule";
        }
        leaf priority {
            type uint16;
            config true;
            mandatory true;
            description "Priority of the FW rule";
         }
        leaf sourceIpAddress {
          type string;
          config true;
          mandatory false;
          description
            "The IP address source";
        }

        leaf destinationIpAddress {
          type string;
          config true;
          mandatory false;
          description
            "The IP address destination";
        }

        leaf sourcePort {
            type string;
            config true;
            mandatory false;
            description
              "The source port";
        }

        leaf destinationPort {
            type string;
            config true;
            mandatory false;
            description
              "The destination port";
        }

        leaf action {
            type enumeration {
              enum "deny" {
                value 1;
                description
                    "Deny = 1";
              }
              enum "allow" {
                value 2;
                description
                  "Allow = 2";
              }
            }
            config true;
            mandatory true;
          }
  }

    grouping conflict-info {
	     leaf priority {
	     	type uint16;
	     	config true;
	     }
	     leaf id {
	     	type uint16;
	     	config true;
	     }
	     leaf vlan-id {
	     	type uint32;
	     	config true;
	     }
	     leaf in-port {
	     	type string;
	     	config true;
	     }
	     leaf dl-src {
	     	type string;
	     	config true;
	     }
	     leaf dl-dst {
	     	type string;
	     	config true;
	     }
	     leaf nw-src {
	     	type string;
	     	config true;
	     }
	     leaf nw-dst {
	     	type string;
	     	config true;
	     }
	     leaf l4-src {
	     	type uint16;
	     	config true;
	     }
	     leaf l4-dst {
	     	type uint16;
	     	config true;
	     }
	     leaf action {
	     	type enumeration {
              enum "BLOCK" {
                value 1;
                description
                    "drop = 1";
              }
              enum "ALLOW" {
                value 2;
                description
                  "forward = 2";
              }
            }
            config true;
	     }
	     leaf protocol {
	     	type enumeration {
              enum "TCP" {
                value 1;
              }
              enum "UDP" {
                value 2;
              }
              enum "ANY" {
                value 3;
              }

            }
            config true;
	     }
	     leaf gen-count {
	     	type uint16;
	     	config true;
	     }
	     leaf sh-count {
	     	type uint16;
	     	config true;
	     }
	     leaf red-count {
	     	type uint16;
	     	config true;
	     }
	     leaf cor-count {
	     	type uint16;
	     	config true;
	     }
	     leaf over-count {
	     	type uint16;
	     	config true;
	     }
	     leaf conflict-type {
	     	type string;
	     	config true;
	     }
	     leaf conflict-group-number {
	     	type uint16;
	     	config true;
	     }
	     leaf resolution {
	     	type boolean;
	     	default true;
	     	config true;
	     }
	     leaf mechanism {
	     	type string;
	     	config true;
	     }
    }

    container fwrule-registry {
        list fwrule-registry-entry {
            key "ruleId";
            uses flowguard:fwrule;
        }
    }
    container conflict-info-registry {
    	list conflictSwitch {
    		key switchId;
    		leaf switchId {
    			type string;
    		}
    		list conflictTable {
    			key "tableId";
    			leaf tableId {
	    			type uint16;
	    			}
    	 		list conflict-group-entry {
    	 			key "id";
    				uses flowguard:conflict-info;
    	 		}
    	 	}
    	 }
    }
    container controls {
        leaf action {
            type enumeration {
              enum "Enable" {
                value 1;
              }
              enum "Disable" {
                value 2;
                description
                  "TCP protocol.";
              }
            }
            config true;
            mandatory false;
          }
        leaf greeting {
            type string;
        }
    }
	container flowguard-status {
		leaf flowguard-status {
			type string;
		}
	}

    rpc flowguard-control {
        input {
            leaf action {
                type enumeration {
                  enum "Enable" {
                    value 1;
                  }
                  enum "Disable" {
                    value 2;
                  }
                }
                config true;
                mandatory false;
              }
        }
        output {
            leaf greeting {
                type string;
            }
        }
    }

    rpc add-fwrule {
        input {
            uses flowguard:fwrule;
        }
        output {
            leaf greeting {
                type string;
            }
        }
    }

    rpc get-conflicts {
    	input {
    		leaf conflict-type {
    			type enumeration {
                  enum "all" {
                    value 1;
                  }
                  enum "GENERALIZATION" {
                    value 2;
                  }
                  enum "SHADOWING" {
                    value 3;
                  }
                  enum "REDUNDANCY" {
                    value 4;
                  }
                  enum "CORRELATION" {
                    value 5;
                  }
                  enum "OVERLAP" {
                    value 6;
                  }
                }
                config true;
                mandatory true;
    		}
    	}
    	output {
    		list conflict-group-list {
    			key "id";
    			uses flowguard:conflict-info;
    		}
    	}
    }
}
